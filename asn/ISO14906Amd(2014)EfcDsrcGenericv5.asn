EfcDsrcGeneric {iso(1) standard(0) 14906 generic(1) version5(5)}
DEFINITIONS AUTOMATIC TAGS ::= BEGIN
EXPORTS ALL;
IMPORTS
GetStampedRq,GetStampedRs{},SetStampedRq{},GetInstanceRq,
GetInstanceRs{},SetInstanceRq{},SetMMIRq,ChannelRq,ChannelRs,CopyRq,
SubRq,AddRq,DebitRq,DebitRs,CreditRq,CreditRs,
EFC-ContextMark,ContractSerialNumber,ContractValidity,
ContractVehicle,ContractAuthenticator,ICC-Id,
ReceiptServicePart,SessionClass,SignedValue,ReceiptServiceSerialNumber,
ReceiptFinancialPart,ReceiptContract,ReceiptOBUId,ReceiptICC-Id,
ReceiptText,ReceiptAuthenticator,ReceiptDistance,LPN,VehicleClass,
VehicleDimensions,VehicleAxles,VehicleWeightLimits,
VehicleWeightLaden,VehicleSpecificCharacteristics,
VehicleAuthenticator,EquipmentOBUId,
EquipmentStatus,DriverCharacteristics,
PaymentMeans,PaymentMeansBalance,PaymentMeansUnit,
PaymentSecurityData,PersonalAccountNumber,ReceiptData1,
ReceiptData2,SessionLocation,ValidityOfContract, AxleWeightLimits, PassengerCapacity, Engine, SoundLevel, ExhaustEmissionValues, DieselEmissionValues, CO2EmissionValue, VehicleTotalDistance, TrailerLicencePlateNumber, TrailerCharacteristics, ActualNumberOfPassengers
FROM EfcDsrcApplication {iso(1) standard(0) 14906 application(0) version5(5)}
CS5
FROM AVIAEINumberingAndDataStructures {iso(1) standard(0) 14816 };
-- defined in ISO 14816 --
-- EXPORTS everything;
Action-Request{Container}::= SEQUENCE{
mode BOOLEAN,
eid Dsrc-EID,
actionType ActionType,
accessCredentials OCTET STRING (SIZE (0..127,...)) OPTIONAL,
actionParameter Container OPTIONAL,
iid Dsrc-EID OPTIONAL
}
Action-Response{Container}::= SEQUENCE{
fill BIT STRING (SIZE(1)),
eid Dsrc-EID,
iid Dsrc-EID OPTIONAL,
responseParameter Container OPTIONAL,
ret ReturnStatus OPTIONAL
}
ActionType ::= INTEGER (0..127,...)
-- 0 : getStamped
-- 1 : setStamped
-- 2 : getSecure
-- 3 : setSecure
-- 4 : getInstance
-- 5 : setInstance
-- 6 : getNonce
-- 7 : setNonce
-- 8 : transferChannel
-- 9 : copy
-- 10 : setMMI
-- 11 : substract
-- 12 : add
-- 13 : debit
-- 14 : credit
-- 15 : echo
-- (16..118) Reserved for ISO/CEN use
-- (119-127) Reserved for private use
ApplicationContextMark ::= EfcContainer (WITH COMPONENTS {octetstring PRESENT})
-- The contents of the octetstring shall be an aligned PER
-- encoding of EFC-Contextmark, but this encoding may be followed
-- by non-standardised encodings. Illustrations of the inclusion
-- of non-standardised encodings are shown in annex B.
ApplicationList ::= SEQUENCE (SIZE (0..127,...)) OF SEQUENCE {
aid DSRCApplicationEntityID,
eid Dsrc-EID OPTIONAL,
parameter ApplicationContextMark OPTIONAL
}

AttributeIdList ::= SEQUENCE (SIZE(0.. 127,...)) OF INTEGER(0..127,...)

AttributeList{Container} ::= SEQUENCE (SIZE(0..127,...)) OF Attributes{Container}

Attributes{Container} ::= SEQUENCE {
	attributeId INTEGER (0..127,...),
	attributeValue Container
}

BeaconID::= SEQUENCE{
	manufacturerid INTEGER(0.. 65535),
	individualid INTEGER(0..134217727)
} -- for registration of manufacturerid see www.nni.nl/cen278

BroadcastPool ::= SEQUENCE{
	directoryvalue Directory,
	content SEQUENCE (SIZE(0..127,...)) OF File
}

BST ::= SEQUENCE{
rsu BeaconID,
time Time,
profile Profile,
mandApplications ApplicationList,
nonmandApplications ApplicationList OPTIONAL,
profileList SEQUENCE (SIZE(0..127,...)) OF Profile
}
EfcContainer ::= CHOICE{
-- The alternative for container and its value is determined
-- from the service primitives.
integer [0] INTEGER,
bitstring [1] BIT STRING,
octetstring [2] OCTET STRING (SIZE (0..127,...)),
universalString [3] UniversalString,
beaconId [4] BeaconID,
t-apdu [5] T-APDUs,
dsrcApplicationEntityId [6] DSRCApplicationEntityID,
dsrc-Ase-Id [7] Dsrc-EID,
attrIdList [8] AttributeIdList,
attrList [9] AttributeList{EfcContainer},
broadcastPool [10] BroadcastPool,
directory [11] Directory,
file [12] File,
fileType [13] FileType,
record [14] Record,
time [15] Time,
vector [16] SEQUENCE (SIZE(0..255)) OF INTEGER(0..127,...),
gstrq [17] GetStampedRq,
gstrs [18] GetStampedRs{EfcContainer},
sstrq [19] SetStampedRq{EfcContainer},
ginrq [20] GetInstanceRq,
ginrs [21] GetInstanceRs{EfcContainer},
sinrq [22] SetInstanceRq{EfcContainer},
charq [23] ChannelRq,
chars [24] ChannelRs,
cpprq [25] CopyRq,
subrq [26] SubRq,
addrq [27] AddRq,
debrq [28] DebitRq,
debrs [29] DebitRs,
crerq [30] CreditRq,
crers [31] CreditRs,
efccontext [32] EFC-ContextMark,
contser [33] ContractSerialNumber,
contval [34] ContractValidity,
contveh [35] ContractVehicle,
contauth [36] ContractAuthenticator,
recspt [37] ReceiptServicePart,
sessioncls [38] SessionClass,
recservserialno [39] ReceiptServiceSerialNumber,
recfinptENV [40] NULL,
reccont [41] ReceiptContract,
recOBUId [42] ReceiptOBUId,
recICCId [43] ReceiptICC-Id,
rectext [44] ReceiptText,
recauth [45] ReceiptAuthenticator,
recdist [46] ReceiptDistance,
vehlpn [47] LPN, -- vehicle licence plate number
vehid [48] CS5, -- vehicle identification number
vehclass [49] VehicleClass,
vehdims [50] VehicleDimensions,
vehaxles [51] VehicleAxles,
vehwtlims [52] VehicleWeightLimits,
vehwtladen [53] VehicleWeightLaden,
vehspchars [54] VehicleSpecificCharacteristics,
vehauth [55] VehicleAuthenticator,
equOBUId [56] EquipmentOBUId,
equICCId [57] ICC-Id,
equstat [58] EquipmentStatus,
dvrchars [59] DriverCharacteristics,
paymeansENV [60] NULL,
paymbal [61] PaymentMeansBalance,
paymunit [62] PaymentMeansUnit,
paysecdata [63] PaymentSecurityData,
paymeans [64] PaymentMeans,
recdata1 [65] ReceiptData1,
recdata2 [66] ReceiptData2,
valofcon [67] ValidityOfContract,
recfinpt [68] ReceiptFinancialPart,
setmmirq [69] SetMMIRq,
awl [70] AxleWeightLimits,
paca [71] PassengerCapacity,
eng [72] Engine,
sl [73] SoundLevel,
eev [74] ExhaustEmissionValues,
dev [75] DieselEmissionValues,
co2ev [76] CO2EmissionValue,
vtd [77] VehicleTotalDistance,
tlpn [78] TrailerLicencePlateNumber,
tch [79] TrailerCharacteristics,
anp [80] ActualNumberOfPassengers,
rfuCenISO48 [81] NULL,
rfuCenISO49 [82] NULL,
rfuCenISO50 [83] NULL,
rfuCenISO51 [84] NULL,
rfuCenISO52 [85] NULL,
rfuCenISO53 [86] NULL,
-- Container CHOICE type values [81..86] are reserved for
-- attribute Ids 48 to 53 which are used in CCC
-- Container CHOICE type values [87..127] are reserved for private EFC use and
-- intended for the addressing of the corresponding private
-- attribute identifiers. Note that container type 87 is also used in LAC
... -- extension marker
-- FIRST NOTE for upcoming revisions of these definitions:
-- EfcContainer should be related to the CccContainer of ISO 12813, LacContainer 
-- of ISO 13141 and SmccContainer of CEN 16702-1 in such a way that: 
-- CccContainer is a concatenation of EfcContainer and ISO 12813 specific attributes,
-- LacContainer is a concatenation of CccContainer and ISO 13141 specific attributes,
-- SmccContainer is a concatenation of LacContainer and CEN 16702-1 specific attributes.
-- Concatenation in this context means a simple adding of attributes to the CHOICE construct
-- SECOND NOTE for upcoming revisions of these definitions:
-- All container types should be OCTET aligned
}
FileType ::= NULL -- not defined
Directory::= SEQUENCE (SIZE(0..127,...)) OF FileName
Dsrc-EID::= INTEGER(0..127, ...)
DSRCApplicationEntityID::= INTEGER {
system (0),
electronic-fee-collection (1),
freight-fleet-management (2),
public-transport (3),
traffic-traveller-information (4),
traffic-control (5),
parking-management (6),
geographic-road-database (7),
medium-range-preinformation (8),
man-machine-interface (9),
intersystem-interface (10),
automatic-vehicle-identification (11),
emergency-warning (12),
private (13),
multi-purpose-payment (14),
dsrc-resource-manager (15),
after-theft-systems (16),
ccc (20),
lac (21)
-- (17..28) are reserved for ISO/CEN DSRC applications
-- (29..30) are reserved for private use
-- 31 is reserved for ISO/CEN-DSRC-applications
}(0..31,...)
-- For the latest standard use of application definition, refer
-- to www.nni.nl/cen278
-- As an example, the application "electronic-fee-collection (1)"
-- is standardised by EN/ISO 14906

Event-Report-Request{Container}::= SEQUENCE{
mode BOOLEAN,
eid Dsrc-EID,
eventType EventType,
accessCredentials OCTET STRING (SIZE(0..127,...)) OPTIONAL,
eventParameter Container OPTIONAL,
iid Dsrc-EID OPTIONAL
}
Event-Report-Response::= SEQUENCE{
fill BIT STRING (SIZE(2)),
eid Dsrc-EID,
iid Dsrc-EID OPTIONAL,
ret ReturnStatus OPTIONAL
}
EventType::= INTEGER{
release (0)
-- (1..118) are reserved for ISO/CEN use
-- (119..127) are reserved for private use
}(0..127,...)
File::=SEQUENCE(SIZE(0..127,...)) OF Record
FileName::= SEQUENCE{
aseID Dsrc-EID,
fileID INTEGER(0..127,...)
}
Get-Request::= SEQUENCE{
fill BIT STRING (SIZE(1)),
eid Dsrc-EID,
accessCredentials OCTET STRING (SIZE(0..127,...)) OPTIONAL,
iid Dsrc-EID OPTIONAL,
attrIdList AttributeIdList OPTIONAL
}
Get-Response{Container}::= SEQUENCE{
fill BIT STRING (SIZE(1)),
eid Dsrc-EID,
iid Dsrc-EID OPTIONAL,
attributelist AttributeList{Container} OPTIONAL,
ret ReturnStatus OPTIONAL
}
Initialisation-Request::= BST
Initialisation-Response::= VST

ObeConfiguration::= SEQUENCE{
equipmentClass INTEGER(0..32767),
manufacturerID INTEGER(0..65535),
obeStatus INTEGER(0..65535) OPTIONAL
-- obeStatus shall always be present. Bit nr 5 of the first octet may indicate the
-- status of the battery: 0 indicates OK, 1 indicates low (xxxB xxxx'H)
}
Profile::= INTEGER {
profile0 (0), -- DSRC Profile 0 as defined in EN 13372
profile1 (1) -- DSRC Profile 1 as defined in EN 13372
-- (2..118) are reserved for ISO/CEN use,
-- (119..127) are reserved for private use
}(0..127,...)
Record::= CHOICE
{simple VisibleString,
...
}
ReturnStatus::= INTEGER {
noError (0),
accessDenied (1),
argumentError (2),
complexityLimitation (3),
processingFailure (4),
processing (5),
chainingError (6)
-- (7..127) are reserved for future CEN use
}(0..127,...)
Set-Request{Container}::= SEQUENCE{
fill BIT STRING (SIZE(1)),
mode BOOLEAN,
eid Dsrc-EID,
accessCredentials OCTET STRING (SIZE(0..127,...)) OPTIONAL,
attrList AttributeList{Container},
iid Dsrc-EID OPTIONAL
}
Set-Response::= SEQUENCE{
fill BIT STRING (SIZE(2)),
eid Dsrc-EID,
iid Dsrc-EID OPTIONAL,
ret ReturnStatus OPTIONAL
}
Time::= INTEGER(0..4294967295)
-- “UNIX time”: number of seconds since midnight at the
-- start of 1st January 1970
T-APDUs-Generic{Container}::=                                               CHOICE{
                action-request                                  [0]   Action-Request{Container},
                action-response                                               [1]   Action-Response{Container},
                event-report-request                    [2]   Event-Report-Request{Container},
                event-report-response                 [3]   Event-Report-Response,
                set-request                                        [4]   Set-Request{Container},
                set-response                                     [5]   Set-Response,
                get-request                                        [6]   Get-Request,
                get-response                                     [7]   Get-Response{Container},
                initialisation-request                      [8]   Initialisation-Request,
                initialisation-response                   [9]   Initialisation-Response
                }


T-APDUs ::= T-APDUs-Generic{EfcContainer}

VST::= SEQUENCE{
fill BIT STRING (SIZE(4)),
profile Profile,
applications ApplicationList,
obeConfiguration ObeConfiguration
}
END
-- Below imported data from ISO 14816's ASN.1 module
-- AVIAEINumberingAndDataStructures {iso(1) standard(0) 14816 }
-- DEFINITIONS AUTOMATIC TAGS ::= BEGIN
-- EXPORTS ALL;
-- CS5 ::= VisibleString
-- CountryCode ::= BIT STRING(SIZE(10))
-- Value assignment is done in accordance with ISO 3166-1 and by
-- using the ITA.2 alphabet.
-- IssuerIdentifier ::= INTEGER(0 .. 16383)
-- See Annex A of ISO 14816 for registration
-- END
